MGIndiaTapModule

DEFINITIONS AUTOMATIC TAGS ::=
BEGIN

MPDispatcherBody ::= SEQUENCE
{
  uid IA5String(SIZE(50)) OPTIONAL,
  token IA5String(SIZE(40)) OPTIONAL,
  applicationID IA5String(SIZE(3)),
  vin IA5String(SIZE(17)) OPTIONAL,
  messageID INTEGER(0..255),
  eventCreationTime INTEGER(0..2147483647),
  eventID INTEGER(0..2147483647) OPTIONAL,
  ulMessageCounter INTEGER(0..65535) OPTIONAL,
  dlMessageCounter INTEGER(0..65535) OPTIONAL,
  ackMessageCounter INTEGER(0..65535) OPTIONAL,
  ackRequired BOOLEAN OPTIONAL,
  applicationDataLength INTEGER(0..65535) OPTIONAL,
  applicationDataEncoding DataEncodingType OPTIONAL,
  applicationDataProtocolVersion INTEGER(0..65535) OPTIONAL,
  testFlag INTEGER(1..3) OPTIONAL,
  result INTEGER(0..65535) OPTIONAL,
  errorMessage OCTET STRING(SIZE(1..1024)) OPTIONAL
}

DataEncodingType ::= ENUMERATED
{
  perUnaligned(0),
  der(1),
  ber(2)
}

OTARVMVehicleStatusReq ::= SEQUENCE
{
  vehStatusReqType INTEGER(0..255)
}

OTARVMVehicleStatusResp513 ::= SEQUENCE
{
  statusTime INTEGER(0..2147483647),
  gpsPosition RvsPosition,
  basicVehicleStatus RvsBasicStatus513,
  extendedVehicleStatus RvsExtStatus OPTIONAL
}

RvsPosition ::= SEQUENCE
{
  wayPoint RvsWayPoint,
  timestamp4Short Timestamp4Short,
  gpsStatus GPSStatus
}

RvsWayPoint ::= SEQUENCE
{
  position RvsWGS84Point,
  heading INTEGER(0..359),
  speed INTEGER(-1000..4500),
  hdop INTEGER(0..1000),
  satellites INTEGER(0..16)
}

RvsWGS84Point ::= SEQUENCE
{
  latitude INTEGER(-90000000..90000000),
  longitude INTEGER(-180000000..180000000),
  altitude INTEGER(-100..8900)
}

Timestamp4Short ::= SEQUENCE
{
  seconds INTEGER(0..2147483647)
}

GPSStatus ::= ENUMERATED
{
  noGpsSignal(0),
  timeFix(1),
  fix2D(2),
  fix3D(3)
}

RvsBasicStatus513 ::= SEQUENCE
{
  driverDoor BOOLEAN,
  passengerDoor BOOLEAN,
  rearLeftDoor BOOLEAN,
  rearRightDoor BOOLEAN,
  bootStatus BOOLEAN,
  bonnetStatus BOOLEAN,
  lockStatus BOOLEAN,
  driverWindow BOOLEAN OPTIONAL,
  passengerWindow BOOLEAN OPTIONAL,
  rearLeftWindow BOOLEAN OPTIONAL,
  rearRightWindow BOOLEAN OPTIONAL,
  sunroofStatus BOOLEAN OPTIONAL,
  frontRrightTyrePressure INTEGER(0..255) OPTIONAL,
  frontLeftTyrePressure INTEGER(0..255) OPTIONAL,
  rearRightTyrePressure INTEGER(0..255) OPTIONAL,
  rearLeftTyrePressure INTEGER(0..255) OPTIONAL,
  wheelTyreMonitorStatus INTEGER(0..255) OPTIONAL,
  sideLightStatus BOOLEAN,
  dippedBeamStatus BOOLEAN,
  mainBeamStatus BOOLEAN,
  vehicleAlarmStatus INTEGER(0..255) OPTIONAL,
  engineStatus INTEGER(0..255),
  powerMode INTEGER(0..255),
  lastKeySeen INTEGER(0..65535),
  currentJourneyDistance INTEGER(0..65535),
  currentJourneyID INTEGER(0..2147483647),
  interiorTemperature INTEGER(-128..127),
  exteriorTemperature INTEGER(-128..127),
  fuelLevelPrc INTEGER(0..255),
  fuelRange INTEGER(0..65535),
  remoteClimateStatus INTEGER(0..255),
  frontLeftSeatHeatLevel INTEGER(0..255) OPTIONAL,
  frontRightSeatHeatLevel INTEGER(0..255) OPTIONAL,
  canBusActive BOOLEAN,
  timeOfLastCANBUSActivity INTEGER(0..2147483647),
  clstrDspdFuelLvlSgmt INTEGER(0..255),
  mileage INTEGER(0..2147483647),
  batteryVoltage INTEGER(0..65535),
  extendedData1 INTEGER(0..2147483647) OPTIONAL,
  extendedData2 INTEGER(0..2147483647) OPTIONAL,
  handBrake BOOLEAN
}

RvsExtStatus ::= SEQUENCE
{
  vehicleAlerts SEQUENCE SIZE(0..64) OF VehicleAlertInfo
}

VehicleAlertInfo ::= SEQUENCE
{
  id INTEGER(0..255),
  value INTEGER(0..255)
}

END
